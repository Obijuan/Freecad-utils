import math


#-- Draw a vector in the z axis
def vectorz(l = 10, l_arrow = 4, d = 1, mark = False, show = True):
	"""Draw a vector in the z axis. Parameters:
		 l : Lenght
         l_arrow: arrow length
		 d : vector diameter
	"""

	#-- Correct the length
	if (l < l_arrow):
		l_arrow = l/2
		
	vectz = Part.makeCylinder(d / 2.0, l - l_arrow)
	base = Part.makeSphere(d / 2.0)
	arrow = Part.makeCone(d/2 + 1, 0.2, l_arrow)
	arrow.Placement.Base.z = l - l_arrow
	
	#-- Create the union of all the parts
	union = vectz.fuse(base)
	union = union.fuse(arrow)
		
	#-- Return de vector z
	return union

def orientate(part, v, vref = App.Vector(0, 0, 1)):
	
	#-- Special cases. Null vector. Ignore
	if v.Length == 0:	
		return
	
	#-- Special case: Vector in the z axis, poiting to the negative
	if v.x == 0 and v.y==0 and v.z < 0:
		raxis = App.Vector(1, 0, 0)
	else:
		raxis = vref.cross(v)
	
	#-- Calculate the rotation angle (in degrees)
	angle = math.degrees(vref.getAngle(v))
	
	#-- Rotate vectz!
	part.Placement.Rotation = App.Rotation(raxis, angle)



def vector(x, y = None, z = None):

	#-- Function overloading. x is mandatory
	if y == None and z == None:
		#-- the first argument is an App.Vector
		v = x
	else:
		#-- The three components are given
		v = App.Vector(x, y, z)
		
	#-- Vector on the z axis
	vectz = vectorz(l = v.Length)
	vref = App.Vector(0, 0, 1)
	
	#------ Orientate vectz on the v direction
	#-- Calculate the rotation axis
	orientate(vectz, v)
	Part.show(vectz)


#---- Main
print("Vector example")

l = 20
vector(l, 0, 0)
vector(0, l, 0)
vector(0, 0, l)
vector(-l, 0, 0)
vector(0, -l, 0)
vector(0, 0, -l)
vector(l, l, l)
vector(-l, l, l)
vector(-l, -l, l)
vector(l, -l, l)
vector(l, l, -l)
vector(-l, l, -l)
vector(-l, -l, -l)
vector(l, -l, -l)
